;;; VezroCAD Drafting Standard v2.0 - AutoCAD 2027 Windows
;;; Use only on a COPY of your document. Requires STB-mode drawing (PSTYLEMODE=0).
;;; Commands VZBW VZCOLOR VZLAYERS
(vl-load-com)
(setq *vz:v2layers* '(

  ("建筑-墙体-轮廓-现状" 8 50 "CONTINUOUS" "VZ-MAIN" 1)
  ("建筑-墙体-轮廓-新建" 30 53 "CONTINUOUS" "VZ-MAIN" 1)
  ("建筑-墙体-轮廓-拆除" 1 35 "DASHED" "VZ-ACCENT" 1)
  ("建筑-墙体-填充-现状" 9 13 "CONTINUOUS" "VZ-FILL" 1)
  ("建筑-墙体-填充-新建" 30 13 "CONTINUOUS" "VZ-FILL" 1)
  ("建筑-墙体-填充-拆除" 1 13 "CONTINUOUS" "VZ-FILL" 1)
  ("建筑-墙体-中心" 8 13 "CENTER" "VZ-FAINT" 1)
  ("建筑-梁体-轮廓-现状" 8 30 "CONTINUOUS" "VZ-MAIN" 1)
  ("建筑-梁体-轮廓-新建" 30 30 "CONTINUOUS" "VZ-MAIN" 1)
  ("建筑-梁体-虚线" 8 15 "DASHED" "VZ-SOFT" 1)
  ("建筑-柱体-轮廓-现状" 8 50 "CONTINUOUS" "VZ-MAIN" 1)
  ("建筑-柱体-轮廓-新建" 30 53 "CONTINUOUS" "VZ-MAIN" 1)
  ("建筑-门体-轮廓-现状" 8 25 "CONTINUOUS" "VZ-MAIN" 1)
  ("建筑-门体-轮廓-新建" 30 25 "CONTINUOUS" "VZ-MAIN" 1)
  ("建筑-门体-开启" 140 15 "CONTINUOUS" "VZ-SOFT" 1)
  ("建筑-门体-门洞" 30 35 "CONTINUOUS" "VZ-MAIN" 1)
  ("建筑-门体-轨迹" 140 15 "DASHED" "VZ-SOFT" 1)
  ("建筑-窗体-轮廓-现状" 8 25 "CONTINUOUS" "VZ-MAIN" 1)
  ("建筑-窗体-轮廓-新建" 30 25 "CONTINUOUS" "VZ-MAIN" 1)
  ("建筑-窗体-开启" 140 15 "CONTINUOUS" "VZ-SOFT" 1)
  ("建筑-楼梯-轮廓" 8 30 "CONTINUOUS" "VZ-MAIN" 1)
  ("建筑-洞口-边界" 1 30 "DASHED" "VZ-MAIN" 1)
  ("建筑-结构-遮挡" 9 15 "DASHED" "VZ-SOFT" 1)
  ("拆改-墙体-定位" 1 20 "CONTINUOUS" "VZ-ACCENT" 1)
  ("拆改-孔洞-标记" 1 25 "CONTINUOUS" "VZ-ACCENT" 1)
  ("拆改-说明-拆除" 1 20 "CONTINUOUS" "VZ-ACCENT" 1)
  ("拆改-说明-新建" 30 20 "CONTINUOUS" "VZ-ACCENT" 1)
  ("装饰-地面-分界" 32 30 "CONTINUOUS" "VZ-MAIN" 1)
  ("装饰-地面-铺贴" 32 15 "CONTINUOUS" "VZ-SOFT" 1)
  ("装饰-地面-填充" 32 13 "CONTINUOUS" "VZ-FILL" 1)
  ("装饰-地面-起铺" 32 20 "CENTER" "VZ-ACCENT" 1)
  ("装饰-地面-门槛" 32 25 "CONTINUOUS" "VZ-MAIN" 1)
  ("装饰-墙面-饰面" 200 25 "CONTINUOUS" "VZ-MAIN" 1)
  ("装饰-墙面-造型" 200 20 "CONTINUOUS" "VZ-MAIN" 1)
  ("装饰-墙面-填充" 200 13 "CONTINUOUS" "VZ-FILL" 1)
  ("装饰-墙面-基层" 200 15 "DASHED" "VZ-SOFT" 1)
  ("装饰-天花-边界" 5 30 "CONTINUOUS" "VZ-MAIN" 1)
  ("装饰-天花-跌级" 5 25 "CONTINUOUS" "VZ-MAIN" 1)
  ("装饰-天花-灯槽" 5 20 "CONTINUOUS" "VZ-MAIN" 1)
  ("装饰-天花-检修" 5 20 "CONTINUOUS" "VZ-SOFT" 1)
  ("装饰-天花-造型" 5 20 "CONTINUOUS" "VZ-MAIN" 1)
  ("装饰-天花-填充" 5 13 "CONTINUOUS" "VZ-FILL" 1)
  ("装饰-背景-造型" 200 30 "CONTINUOUS" "VZ-MAIN" 1)
  ("装饰-踢脚-轮廓" 32 18 "CONTINUOUS" "VZ-SOFT" 1)
  ("装饰-石材-拼缝" 32 15 "CONTINUOUS" "VZ-SOFT" 1)
  ("装饰-线条-轮廓" 200 18 "CONTINUOUS" "VZ-SOFT" 1)
  ("定制-衣柜-柜体" 6 30 "CONTINUOUS" "VZ-MAIN" 1)
  ("定制-衣柜-柜门" 6 20 "CONTINUOUS" "VZ-MAIN" 1)
  ("定制-衣柜-开启" 6 15 "DASHED" "VZ-SOFT" 1)
  ("定制-衣柜-填充" 6 13 "CONTINUOUS" "VZ-FILL" 1)
  ("定制-橱柜-柜体" 6 30 "CONTINUOUS" "VZ-MAIN" 1)
  ("定制-橱柜-台面" 6 30 "CONTINUOUS" "VZ-MAIN" 1)
  ("定制-橱柜-柜门" 6 20 "CONTINUOUS" "VZ-MAIN" 1)
  ("定制-橱柜-五金" 6 15 "CONTINUOUS" "VZ-SOFT" 1)
  ("定制-鞋柜-柜体" 6 30 "CONTINUOUS" "VZ-MAIN" 1)
  ("定制-其他-柜体" 6 30 "CONTINUOUS" "VZ-MAIN" 1)
  ("定制-柜体-遮罩" 6 13 "CONTINUOUS" "VZ-MASK" 1)
  ("定制-柜体-内构" 6 18 "CONTINUOUS" "VZ-SOFT" 1)
  ("家具-活动-轮廓" 140 25 "CONTINUOUS" "VZ-MAIN" 1)
  ("家具-活动-细节" 140 15 "CONTINUOUS" "VZ-SOFT" 1)
  ("家具-活动-填充" 140 13 "CONTINUOUS" "VZ-FILL" 1)
  ("家具-软装-轮廓" 140 18 "CONTINUOUS" "VZ-SOFT" 1)
  ("家具-家电-轮廓" 140 25 "CONTINUOUS" "VZ-MAIN" 1)
  ("家具-家电-开启" 140 15 "DASHED" "VZ-SOFT" 1)
  ("电气-照明-灯具" 5 25 "CONTINUOUS" "VZ-MAIN" 1)
  ("电气-照明-灯带" 5 20 "CONTINUOUS" "VZ-MAIN" 1)
  ("电气-照明-回路" 5 15 "DASHED" "VZ-SOFT" 1)
  ("电气-强电-插座" 1 25 "CONTINUOUS" "VZ-ACCENT" 1)
  ("电气-强电-开关" 1 25 "CONTINUOUS" "VZ-ACCENT" 1)
  ("电气-强电-线路" 1 15 "DASHED" "VZ-SOFT" 1)
  ("电气-强电-配电" 1 30 "CONTINUOUS" "VZ-ACCENT" 1)
  ("电气-弱电-面板" 200 25 "CONTINUOUS" "VZ-MAIN" 1)
  ("电气-弱电-线路" 200 15 "DASHED" "VZ-SOFT" 1)
  ("电气-智能-设备" 200 25 "CONTINUOUS" "VZ-MAIN" 1)
  ("电气-设备-定位" 5 13 "CENTER" "VZ-FAINT" 1)
  ("给排-给水-冷水" 5 20 "CONTINUOUS" "VZ-MAIN" 1)
  ("给排-给水-热水" 1 20 "CONTINUOUS" "VZ-MAIN" 1)
  ("给排-排水-污水" 200 25 "CONTINUOUS" "VZ-MAIN" 1)
  ("给排-排水-废水" 140 25 "CONTINUOUS" "VZ-MAIN" 1)
  ("给排-设备-定位" 140 20 "CONTINUOUS" "VZ-MAIN" 1)
  ("给排-洁具-轮廓" 140 25 "CONTINUOUS" "VZ-MAIN" 1)
  ("给排-管道-立管" 200 30 "CONTINUOUS" "VZ-MAIN" 1)
  ("给排-防水-范围" 140 15 "DASHED" "VZ-FAINT" 1)
  ("暖通-空调-设备" 140 25 "CONTINUOUS" "VZ-MAIN" 1)
  ("暖通-空调-管线" 140 20 "DASHED" "VZ-SOFT" 1)
  ("暖通-新风-设备" 140 25 "CONTINUOUS" "VZ-MAIN" 1)
  ("暖通-新风-管线" 140 20 "DASHED" "VZ-SOFT" 1)
  ("暖通-采暖-散热" 1 25 "CONTINUOUS" "VZ-MAIN" 1)
  ("暖通-采暖-管线" 1 20 "DASHED" "VZ-SOFT" 1)
  ("暖通-排风-设备" 140 25 "CONTINUOUS" "VZ-MAIN" 1)
  ("标注-尺寸-建筑" 8 15 "CONTINUOUS" "VZ-MAIN" 1)
  ("标注-尺寸-装饰" 32 15 "CONTINUOUS" "VZ-MAIN" 1)
  ("标注-尺寸-定制" 6 15 "CONTINUOUS" "VZ-MAIN" 1)
  ("标注-尺寸-机电" 5 15 "CONTINUOUS" "VZ-MAIN" 1)
  ("标注-文字-说明" 8 18 "CONTINUOUS" "VZ-MAIN" 1)
  ("标注-文字-材料" 8 18 "CONTINUOUS" "VZ-MAIN" 1)
  ("标注-编号-空间" 8 20 "CONTINUOUS" "VZ-MAIN" 1)
  ("标注-编号-门窗" 8 18 "CONTINUOUS" "VZ-MAIN" 1)
  ("标注-索引-立面" 1 25 "CONTINUOUS" "VZ-ACCENT" 1)
  ("标注-索引-节点" 1 25 "CONTINUOUS" "VZ-ACCENT" 1)
  ("标注-标高-地面" 32 20 "CONTINUOUS" "VZ-MAIN" 1)
  ("标注-标高-顶面" 5 20 "CONTINUOUS" "VZ-MAIN" 1)
  ("标注-引线-说明" 8 15 "CONTINUOUS" "VZ-MAIN" 1)
  ("标注-符号-定位" 8 18 "CONTINUOUS" "VZ-MAIN" 1)
  ("标注-轴网-轴线" 8 13 "CENTER" "VZ-FAINT" 1)
  ("标注-符号-指北" 8 20 "CONTINUOUS" "VZ-MAIN" 1)
  ("图纸-图框-边线" 8 50 "CONTINUOUS" "VZ-MAIN" 1)
  ("图纸-图签-文字" 8 18 "CONTINUOUS" "VZ-MAIN" 1)
  ("图纸-图签-表格" 8 20 "CONTINUOUS" "VZ-MAIN" 1)
  ("图纸-视口-边界" 9 13 "CONTINUOUS" "VZ-FAINT" 0)
  ("图纸-水印-标识" 9 18 "CONTINUOUS" "VZ-FAINT" 1)
  ("图纸-图例-线样" 8 20 "CONTINUOUS" "VZ-MAIN" 1)
  ("辅助-参考-底图" 9 13 "CONTINUOUS" "VZ-FAINT" 0)
  ("辅助-参考-点位" 9 13 "CONTINUOUS" "VZ-FAINT" 0)
  ("辅助-几何-定位" 9 13 "CONTINUOUS" "VZ-FAINT" 0)
  ("辅助-几何-施工" 9 13 "CONTINUOUS" "VZ-FAINT" 0)
  ("辅助-分析-检测" 9 13 "CONTINUOUS" "VZ-FAINT" 0)
  ("辅助-视口-规则" 9 13 "CONTINUOUS" "VZ-FAINT" 0)
  ("分析-收纳-填色" 6 13 "CONTINUOUS" "VZ-FILL" 1)
  ("分析-材料-分区" 32 13 "CONTINUOUS" "VZ-FILL" 1)
  ("分析-面积-边界" 140 18 "CONTINUOUS" "VZ-SOFT" 1)
  ("分析-动线-路径" 200 20 "CONTINUOUS" "VZ-ACCENT" 1)
  ("通用-图块-主轮" 7 35 "CONTINUOUS" "VZ-MAIN" 1)
  ("通用-图块-次轮" 8 25 "CONTINUOUS" "VZ-MAIN" 1)
  ("通用-图块-细线" 9 15 "CONTINUOUS" "VZ-SOFT" 1)
  ("通用-图块-隐线" 9 15 "DASHED" "VZ-SOFT" 1)
  ("通用-图块-填充" 9 13 "CONTINUOUS" "VZ-FILL" 1)
  ("通用-图块-遮罩" 7 13 "CONTINUOUS" "VZ-MASK" 1)
  ("通用-图块-定位" 9 13 "CONTINUOUS" "VZ-FAINT" 0)
  ("建筑-门体-细节" 140 15 "CONTINUOUS" "VZ-SOFT" 1)
  ("建筑-门体-遮罩" 7 13 "CONTINUOUS" "VZ-MASK" 1)
  ("建筑-窗体-细节" 140 15 "CONTINUOUS" "VZ-SOFT" 1)
  ("建筑-窗体-遮罩" 7 13 "CONTINUOUS" "VZ-MASK" 1)
  ("定制-柜门-细节" 6 15 "CONTINUOUS" "VZ-SOFT" 1)
  ("定制-柜体-隐线" 6 15 "DASHED" "VZ-SOFT" 1)
  ("定制-柜体-填充" 6 13 "CONTINUOUS" "VZ-FILL" 1)
  ("家具-活动-遮罩" 7 13 "CONTINUOUS" "VZ-MASK" 1)
  ("给排-洁具-遮罩" 7 13 "CONTINUOUS" "VZ-MASK" 1)
  ("装饰-天花-隐线" 5 15 "DASHED" "VZ-SOFT" 1)
  ("装饰-地面-分格" 32 15 "CONTINUOUS" "VZ-SOFT" 1)
  ("电气-灯具-遮罩" 7 13 "CONTINUOUS" "VZ-MASK" 1)
  ("标注-索引-细线" 7 15 "CONTINUOUS" "VZ-MAIN" 1)
))
(defun vz:tryput (object property value / result)
 (setq result (vl-catch-all-apply 'vlax-put-property (list object property value)))
 (not (vl-catch-all-error-p result)))
(defun vz:sheet (name / doc layout)
 (if (/= (getvar "PSTYLEMODE") 0)
   (princ "\nPlease convert a COPY of this CTB drawing to STB before continuing.")
   (progn
     (setq doc (vla-get-ActiveDocument (vlax-get-acad-object)))
     (setq layout (vla-get-ActiveLayout doc))
     (if (vz:tryput layout 'StyleSheet name)
       (progn
         (vz:tryput layout 'PlotWithPlotStyles :vlax-true)
         (princ (strcat "\nActive layout: " name " (other layouts unchanged).")))
       (princ (strcat "\nCannot set " name "; check STYLESMANAGER path.")))))
 (princ))
(defun c:VZBW () (vz:sheet "VZ-A3-BW.stb"))
(defun c:VZCOLOR () (vz:sheet "VZ-A3-COLOR.stb"))
(defun vz:linetype (doc name / result)
 (if (and (/= name "CONTINUOUS") (not (tblsearch "LTYPE" name)))
   (setq result (vl-catch-all-apply 'vla-Load (list (vla-get-Linetypes doc) name "acadiso.lin"))))
 )
(defun c:VZLAYERS (/ doc table row ly new skipped failed)
 (if (/= (getvar "PSTYLEMODE") 0)
   (princ "\nPSTYLEMODE=1. Use STB mode on a COPY; current document unchanged.")
   (progn
     (setq doc (vla-get-ActiveDocument (vlax-get-acad-object))
           table (vla-get-Layers doc) new 0 skipped 0 failed 0)
     (foreach row *vz:v2layers*
       (if (tblsearch "LAYER" (car row))
         (setq skipped (1+ skipped))
         (progn
           (vz:linetype doc (nth 3 row))
           (setq ly (vla-Add table (car row)))
           (vla-put-Color ly (nth 1 row))
           (vla-put-Lineweight ly (nth 2 row))
           (if (tblsearch "LTYPE" (nth 3 row))
             (vla-put-Linetype ly (nth 3 row)))
           (vla-put-Plottable ly (if (= (nth 5 row) 1) :vlax-true :vlax-false))
           (if (not (vz:tryput ly 'PlotStyleName (nth 4 row)))
             (setq failed (1+ failed)))
           (setq new (1+ new)))))
     (princ (strcat "\nCreated: " (itoa new) "; skipped existing: " (itoa skipped) "; style failures: " (itoa failed)))
     (if (> failed 0)
       (princ "\nSet VZBW/VZCOLOR on active layout, then manually inspect Layer Plot Styles."))))
 (princ))
(princ "\nLoaded V2. Commands: VZBW / VZCOLOR / VZLAYERS")
(princ)
